-- Vendored verbatim from https://github.com/wineslab/libe3 messages/asn1/V1/e3ap-1.0.0.asn1
-- at commit f2329e0 (tag 0.2.1, 2026-09-22) for the OCUDU <-> libe3
-- interoperability tests in python/tests/test_libe3_interop.py. Do not edit; re-vendor.
-- SPDX-FileCopyrightText: Copyright (c) 2026 Northeastern University
-- SPDX-License-Identifier: Apache-2.0

E3 DEFINITIONS AUTOMATIC TAGS ::= BEGIN

    E3-SetupRequest ::= SEQUENCE {
        e3apProtocolVersion  E3-Version,
        dAppName             UTF8String (SIZE (1..64)),
        dAppVersion          E3-Version,
        vendor               UTF8String (SIZE (1..64)),
        ...
    }

    E3-SetupResponse ::= SEQUENCE {
        requestId            E3-MessageID,
        responseCode         E3-ResponseCode,
        ranIdentifier        UTF8String (SIZE (1..64)),
        e3apProtocolVersion  E3-Version OPTIONAL,
        dAppIdentifier       E3-DAppID OPTIONAL,
        ranFunctionList      SEQUENCE OF E3-RanFunctionDefinition OPTIONAL,
        ...
    }

    E3-SubscriptionRequest ::= SEQUENCE {
        dAppIdentifier          E3-DAppID,
        ranFunctionIdentifier   INTEGER (1..65535),
        telemetryIdentifierList SEQUENCE (SIZE (0..1000)) OF INTEGER (1..65535),
        controlIdentifierList   SEQUENCE (SIZE (0..1000)) OF INTEGER (1..65535),
        subscriptionTime        INTEGER (0..3600) OPTIONAL,
        periodicity             INTEGER (0..1000) OPTIONAL,
        ...
    }

    E3-SubscriptionDelete ::= SEQUENCE {
        dAppIdentifier        E3-DAppID,
        subscriptionId        INTEGER (1..65535),
        ...
    }

    E3-SubscriptionResponse ::= SEQUENCE {
        requestId            E3-MessageID,
        dAppIdentifier       E3-DAppID,
        responseCode         E3-ResponseCode,
        subscriptionId       INTEGER (1..65535) OPTIONAL,
        telemetryIdentifierList SEQUENCE (SIZE (0..1000)) OF INTEGER (1..65535) OPTIONAL,
        controlIdentifierList   SEQUENCE (SIZE (0..1000)) OF INTEGER (1..65535) OPTIONAL,
        ...
    }

    E3-RanFunctionDefinition ::= SEQUENCE {
        ranFunctionIdentifier   INTEGER (1..65535),
        telemetryIdentifierList SEQUENCE (SIZE (0..1000)) OF INTEGER (1..65535),
        controlIdentifierList   SEQUENCE (SIZE (0..1000)) OF INTEGER (1..65535),
        ranFunctionData         OCTET STRING (SIZE (1..32768)),
        ...
    }

    E3-IndicationMessage ::= SEQUENCE {
        dAppIdentifier          E3-DAppID,
        ranFunctionIdentifier   INTEGER (1..65535),
        protocolData            OCTET STRING (SIZE (1..32768)),
        ...
    }

    E3-DAppControlAction ::= SEQUENCE {
        dAppIdentifier          E3-DAppID,
        ranFunctionIdentifier   INTEGER (1..65535),
        controlIdentifier       INTEGER (1..65535),
        -- Present only when the dApp is re-issuing a control it received as an
        -- E3-XAppControlAction, carrying that action's sequenceId back down so the
        -- RAN can match the applied control to the xApp procedure that asked for
        -- it. Absent on a control the dApp decided on its own.
        sequenceId              E3-SequenceID OPTIONAL,
        actionData              OCTET STRING (SIZE (1..32768)),
        ...
    }

    E3-DAppReport ::= SEQUENCE {
        dAppIdentifier          E3-DAppID,
        ranFunctionIdentifier   INTEGER (1..65535),
        -- Assigned by the dApp. A report is the head of the E2-E3 loop, so this is
        -- the identifier every later message in that procedure carries: the RAN
        -- copies it into the E2SM-DAPP indication header as sequence-id, and an
        -- xApp reacting to this report echoes it on its control.
        sequenceId              E3-SequenceID,
        reportData              OCTET STRING (SIZE (1..32768)),
        ...
    }

    E3-XAppControlAction ::= SEQUENCE {
        dAppIdentifier          E3-DAppID,
        ranFunctionIdentifier   INTEGER (1..65535),
        -- Copied by the RAN's E2-E3 bridge from the E2SM-DAPP control header's
        -- sequence-id. Mandatory: a relayed xApp control that carried no id could
        -- never be matched to the control acknowledge the RAN owes the xApp.
        sequenceId              E3-SequenceID,
        xAppControlData         OCTET STRING (SIZE (1..32768)),
        ...
    }

    E3-ReleaseMessage ::= SEQUENCE {
        dAppIdentifier       E3-DAppID,
        ...
    }

    E3-MessageAck ::= SEQUENCE {
        requestId            E3-MessageID,
        responseCode         E3-ResponseCode,
        ...
    }

    -- Correlation identifier for one detection-to-mitigation procedure, assigned
    -- by whichever component originates it and propagated unchanged by everyone
    -- downstream. It is what crosses into E2SM-DAPP as sequence-id, so the E2 and
    -- E3 legs of a loop join per message instead of by nearest-in-time pairing.
    --
    -- Same range as E3-MessageID deliberately: both are producer-assigned counters
    -- with the same lifetime, and a shared range means neither can silently
    -- truncate when one is stored in a field sized for the other. Unlike a message
    -- id it is not reassigned per hop.
    E3-SequenceID ::= INTEGER (1..4294967295)

    E3-DAppID ::= INTEGER (1..65535)
    E3-MessageID ::= INTEGER (1..4294967295)
    E3-Version ::= UTF8String (SIZE (1..11))
    -- Deliberately not extensible. An extensible ENUMERATED makes asn1c pass
    -- unknown values through as bare integers, which would turn every
    -- response-code switch in the encoders into a partial function. Adding a
    -- response code is a wire change we are willing to pay for explicitly.
    E3-ResponseCode ::= ENUMERATED { positive(0), negative(1) }

    -- Nanoseconds since the Unix epoch on the realtime (UTC) clock. Never
    -- subtract it from a monotonic stamp.
    --
    -- Absent means "no producer reference", which is a normal message, not a
    -- malformed one: a producer that does not want the clock read on its data
    -- path simply omits it.
    --
    -- Unconstrained on purpose. asn1c renders this as a native signed integer
    -- and APER length-prefixes it, so the field widens by itself instead of
    -- capping the range, and the codec stays allocation-free on the
    -- indication path.
    --
    -- Do not "tighten" this to INTEGER (0..MAX): a semi-constrained INTEGER is
    -- APC_SEMI_CONSTRAINED, and asn1c 0.9.29's APER decoder has no branch for
    -- that flag and fails every decode. An explicit upper bound works but
    -- forces the arbitrary-precision INTEGER_t and a heap allocation per PDU.
    E3-Timestamp ::= INTEGER

    E3-PDU ::= SEQUENCE {
        id        E3-MessageID,
        timestamp E3-Timestamp OPTIONAL,
        msg       CHOICE {
            setupRequest          [0]  E3-SetupRequest,
            setupResponse         [1]  E3-SetupResponse,
            subscriptionRequest   [2]  E3-SubscriptionRequest,
            subscriptionDelete    [3]  E3-SubscriptionDelete,
            subscriptionResponse  [4]  E3-SubscriptionResponse,
            indicationMessage     [5]  E3-IndicationMessage,
            dAppControlAction     [6]  E3-DAppControlAction,
            dAppReport            [7]  E3-DAppReport,
            xAppControlAction     [8]  E3-XAppControlAction,
            releaseMessage        [9]  E3-ReleaseMessage,
            messageAck            [10] E3-MessageAck,
            ...
        },
        ...
    }

END
