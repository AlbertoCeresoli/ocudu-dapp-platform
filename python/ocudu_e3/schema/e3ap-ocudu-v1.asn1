-- SPDX-FileCopyrightText: Copyright (C) 2026 DeepSig Inc.
-- SPDX-License-Identifier: BSD-3-Clause-Clear

E3AP-OCUDU-V1 DEFINITIONS AUTOMATIC TAGS ::= BEGIN

-- E3 application protocol used by out-of-process dApps and observers that
-- reach the embedded OCUDU E3 agent over SCTP.
--
-- The procedure set and field names mirror E3AP 1.0.0 as implemented by the
-- Northeastern University libe3 project (setup, subscription, indication,
-- dApp control action, dApp report, xApp control action, release, message
-- ack) so that dApp logic ports between the stacks. The module is not
-- byte-compatible with libe3: every SEQUENCE is extensible, identifier ranges
-- are wide enough for production deployments, payloads are bounded at
-- 16 MiB with explicit fragmentation, a control response carries a
-- service-model outcome instead of a bare acknowledgement, and bulk tensors
-- may be delivered by reference through a shared-memory region. The envelope
-- carries the same optional nanosecond timestamp as libe3 0.0.11 and later.
--
-- Service-model bodies are opaque APER OCTET STRINGs selected by
-- ranFunctionIdentifier. Registered RAN functions:
--   10  OCUDU-TELEMETRY-SM           (indications: Telemetry-IndicationData,
--                                     subscriptionData: Telemetry-SubscriptionData)
--   11  E3SM-OCUDU-DAPP-MGMT-V1      (actionData: ManagementRequest,
--                                     controlOutcome: ManagementResponse)
--
-- Transport: one E3-PDU per SCTP message on a one-to-one style association.
-- SCTP stream 0 carries procedures; stream 1 carries indications. Payload
-- protocol identifier 0x00E3A001 is a project-private value. Payloads larger
-- than one fragment are split into ordered fragments of at most
-- maxE3FragmentBytes; receivers reassemble fragments that share the same
-- PDU id (control) or subscriptionId + sequence (indication) in fragmentIndex
-- order and verify the reassembled length against payloadBytes before
-- decoding. Linux SCTP cannot deliver a single message larger than the socket
-- send buffer, so senders MUST fragment rather than rely on the transport.

maxE3Name          INTEGER ::= 64
maxE3Version       INTEGER ::= 32
maxE3Text          INTEGER ::= 512
maxE3RanFunctions  INTEGER ::= 64
maxE3Identifiers   INTEGER ::= 256
-- Largest reassembled opaque service-model payload (16 MiB).
maxE3PayloadBytes  INTEGER ::= 16777216
-- Largest payload fragment carried by one PDU (64 KiB).
maxE3FragmentBytes INTEGER ::= 65536
-- Largest RAN-function capability blob in one setup response.
maxE3FunctionData  INTEGER ::= 262144

E3-DAppID ::= INTEGER (1..65535)
E3-MessageID ::= INTEGER (1..4294967295)
E3-RanFunctionID ::= INTEGER (1..65535)
E3-TelemetryID ::= INTEGER (1..65535)
E3-ControlID ::= INTEGER (1..65535)
E3-SubscriptionID ::= INTEGER (1..65535)
-- Bounded UTF-8 text carried as OCTET STRING: PER does not make SIZE constraints
-- on UTF8String visible, and encoders disagree on that corner; OCTET STRING keeps
-- every implementation byte-identical. Receivers MUST reject malformed UTF-8.
E3-Version ::= OCTET STRING (SIZE (1..maxE3Version))
E3-Name ::= OCTET STRING (SIZE (1..maxE3Name))
E3-Text ::= OCTET STRING (SIZE (0..maxE3Text))
E3-Identifier ::= OCTET STRING (SIZE (16))
E3-Unsigned64 ::= OCTET STRING (SIZE (8))
E3-PayloadFragment ::= OCTET STRING (SIZE (1..maxE3FragmentBytes))
E3-ResponseCode ::= ENUMERATED { positive(0), negative(1), ... }

E3-Cause ::= ENUMERATED {
  unspecified(0), protocolError(1), setupRequired(2), setupAlreadyComplete(3),
  unsupportedProtocolVersion(4), unsupportedRanFunction(5), unsupportedIdentifier(6),
  invalidRequest(7), notFound(8), duplicate(9), resourceExhausted(10),
  authorizationRejected(11), payloadTooLarge(12), transportOverrun(13),
  shuttingDown(14), ...
}

E3-IdentifierList ::= SEQUENCE (SIZE (0..maxE3Identifiers)) OF INTEGER (1..65535)

-- Nanoseconds since the Unix epoch on the realtime (UTC) clock, mirroring the
-- libe3 E3AP 1.0.0 envelope timestamp field for field. Absent means "no
-- producer reference". Unconstrained on purpose: asn1c renders it as a native
-- 64-bit integer and APER length-prefixes it.
E3-Timestamp ::= INTEGER

-- ===========================================================================
-- By-reference bulk data. A subscription may ask for large tensors to be
-- delivered through a shared-memory region instead of in-band fragments. The
-- RAN maps one region per subscription, advertises it once in the
-- subscription response, writes each tensor into the next row, and sends an
-- indication whose protocolData carries the service-model record with its
-- bulk field empty plus an E3-TensorDescriptor locating the bytes. Enumerator
-- values mirror the Class-C OCC3 metadata (class-c-publication-v1.fbs) so a
-- descriptor and the metadata it accompanies never disagree.
-- ===========================================================================

E3-DeliveryMode ::= ENUMERATED { inBand(0), byReference(1), ... }

E3-MemoryDomain ::= ENUMERATED {
  host(0), hostPinned(1), acceleratorDevice(2), managedCoherent(3),
  posixShared(4), acceleratorIpcExport(5), ...
}

E3-ElementType ::= ENUMERATED {
  int8(0), uint8(1), int16(2), uint16(3), int32(4), fp16(5), bf16(6), fp32(7),
  complexInt16(8), complexBf16(9), complexFp16(10), complexFp32(11), ...
}

-- One POSIX shared-memory region the RAN maps for a subscription. Layout:
-- a 64-byte region header followed by nofRows rows of rowBytes; each row
-- starts with a 64-byte row header carrying a seqlock generation, the
-- publication sequence and the byte length, followed by the tensor bytes.
-- Readers re-check the row generation after copying.
E3-SharedRegion ::= SEQUENCE {
  memoryDomain  E3-MemoryDomain,
  regionName    E3-Name,
  regionBytes   E3-Unsigned64,
  headerBytes   INTEGER (0..65535),
  rowBytes      E3-Unsigned64,
  nofRows       INTEGER (1..65535),
  layoutVersion INTEGER (0..65535),
  ...
}

-- Locates one published tensor for a CPU consumer (shared region row) or a
-- GPU consumer (accelerator IPC export, mirroring the Class-C CUDA export
-- slot: opaque 64-byte memory and ready-event handles interpreted only by
-- the matching accelerator runtime).
E3-TensorLocation ::= CHOICE {
  posixShared SEQUENCE {
    regionName E3-Name,
    rowIndex   INTEGER (0..65535),
    byteOffset E3-Unsigned64,
    ...
  },
  acceleratorIpc SEQUENCE {
    deviceOrdinal    INTEGER (0..65535),
    allocationId     E3-Unsigned64,
    memoryHandle     OCTET STRING (SIZE (64)),
    readyEventHandle OCTET STRING (SIZE (64)) OPTIONAL,
    byteOffset       E3-Unsigned64,
    ...
  },
  ...
}

E3-TensorDescriptor ::= SEQUENCE {
  memoryDomain  E3-MemoryDomain,
  location      E3-TensorLocation,
  byteLength    E3-Unsigned64,
  -- Row (or slot) generation at publication; a reader that observes a
  -- different value after copying has read a torn row and must discard it.
  generation    E3-Unsigned64,
  elementType   E3-ElementType OPTIONAL,
  dimensions    SEQUENCE (SIZE (1..8)) OF INTEGER (0..4294967295) OPTIONAL,
  byteStrides   SEQUENCE (SIZE (1..8)) OF E3-Unsigned64 OPTIONAL,
  layoutId      INTEGER (0..65535) OPTIONAL,
  leaseExpiryNs E3-Unsigned64 OPTIONAL,
  ...
}

E3-RanFunctionDefinition ::= SEQUENCE {
  ranFunctionIdentifier   E3-RanFunctionID,
  telemetryIdentifierList E3-IdentifierList,
  controlIdentifierList   E3-IdentifierList,
  ranFunctionData         OCTET STRING (SIZE (1..maxE3FunctionData)),
  ...,
  ranFunctionName         E3-Name OPTIONAL,
  ranFunctionVersion      E3-Version OPTIONAL
}

E3-SetupRequest ::= SEQUENCE {
  e3apProtocolVersion E3-Version,
  dAppName            E3-Name,
  dAppVersion         E3-Version,
  vendor              E3-Name,
  ...,
  dAppInstance        E3-Identifier OPTIONAL
}

E3-SetupResponse ::= SEQUENCE {
  requestId           E3-MessageID,
  responseCode        E3-ResponseCode,
  ranIdentifier       E3-Name,
  e3apProtocolVersion E3-Version OPTIONAL,
  dAppIdentifier      E3-DAppID OPTIONAL,
  ranFunctionList     SEQUENCE (SIZE (0..maxE3RanFunctions)) OF E3-RanFunctionDefinition OPTIONAL,
  ...,
  cause               E3-Cause OPTIONAL,
  detail              E3-Text OPTIONAL,
  ranInstance         E3-Identifier OPTIONAL,
  maximumPayloadBytes INTEGER (1..maxE3PayloadBytes) OPTIONAL,
  maximumFragmentBytes INTEGER (1..maxE3FragmentBytes) OPTIONAL
}

E3-SubscriptionRequest ::= SEQUENCE {
  dAppIdentifier          E3-DAppID,
  ranFunctionIdentifier   E3-RanFunctionID,
  telemetryIdentifierList E3-IdentifierList,
  controlIdentifierList   E3-IdentifierList,
  subscriptionTime        INTEGER (0..86400) OPTIONAL,
  periodicity             INTEGER (0..60000) OPTIONAL,
  ...,
  -- Service-model subscription parameters (E2-style action definition).
  subscriptionData        OCTET STRING (SIZE (1..maxE3FunctionData)) OPTIONAL,
  -- Ask for bulk tensors by reference; the response advertises the region.
  deliveryMode            E3-DeliveryMode OPTIONAL,
  -- Objects whose tensor is smaller than this stay in band (default: one fragment).
  minimumByReferenceBytes INTEGER (0..maxE3PayloadBytes) OPTIONAL
}

E3-SubscriptionDelete ::= SEQUENCE {
  dAppIdentifier E3-DAppID,
  subscriptionId E3-SubscriptionID,
  ...
}

E3-SubscriptionResponse ::= SEQUENCE {
  requestId               E3-MessageID,
  dAppIdentifier          E3-DAppID,
  responseCode            E3-ResponseCode,
  subscriptionId          E3-SubscriptionID OPTIONAL,
  telemetryIdentifierList E3-IdentifierList OPTIONAL,
  controlIdentifierList   E3-IdentifierList OPTIONAL,
  ...,
  cause                   E3-Cause OPTIONAL,
  detail                  E3-Text OPTIONAL,
  -- Present when deliveryMode byReference was granted.
  sharedRegion            E3-SharedRegion OPTIONAL
}

E3-IndicationMessage ::= SEQUENCE {
  dAppIdentifier        E3-DAppID,
  ranFunctionIdentifier E3-RanFunctionID,
  protocolData          E3-PayloadFragment,
  ...,
  subscriptionId        E3-SubscriptionID OPTIONAL,
  telemetryIdentifier   E3-TelemetryID OPTIONAL,
  sequence              E3-Unsigned64 OPTIONAL,
  fragmentIndex         INTEGER (0..65535) DEFAULT 0,
  fragmentCount         INTEGER (1..65536) DEFAULT 1,
  payloadBytes          INTEGER (1..maxE3PayloadBytes) OPTIONAL,
  -- Present when the record's bulk field was delivered by reference.
  byReference           E3-TensorDescriptor OPTIONAL
}

E3-DAppControlAction ::= SEQUENCE {
  dAppIdentifier        E3-DAppID,
  ranFunctionIdentifier E3-RanFunctionID,
  controlIdentifier     E3-ControlID,
  actionData            E3-PayloadFragment,
  ...,
  fragmentIndex         INTEGER (0..65535) DEFAULT 0,
  fragmentCount         INTEGER (1..65536) DEFAULT 1,
  payloadBytes          INTEGER (1..maxE3PayloadBytes) OPTIONAL
}

-- Outcome of a dApp control action carrying a service-model response body.
-- libe3 answers control actions with E3-MessageAck only; OCUDU sends the ack
-- when the request is accepted for processing and this message when the
-- service model produces a result.
E3-ControlResponse ::= SEQUENCE {
  requestId             E3-MessageID,
  dAppIdentifier        E3-DAppID,
  ranFunctionIdentifier E3-RanFunctionID,
  controlIdentifier     E3-ControlID,
  responseCode          E3-ResponseCode,
  cause                 E3-Cause OPTIONAL,
  detail                E3-Text OPTIONAL,
  controlOutcome        E3-PayloadFragment OPTIONAL,
  fragmentIndex         INTEGER (0..65535) DEFAULT 0,
  fragmentCount         INTEGER (1..65536) DEFAULT 1,
  payloadBytes          INTEGER (0..maxE3PayloadBytes) DEFAULT 0,
  ...
}

E3-DAppReport ::= SEQUENCE {
  dAppIdentifier        E3-DAppID,
  ranFunctionIdentifier E3-RanFunctionID,
  reportData            E3-PayloadFragment,
  ...
}

E3-XAppControlAction ::= SEQUENCE {
  dAppIdentifier        E3-DAppID,
  ranFunctionIdentifier E3-RanFunctionID,
  xAppControlData       E3-PayloadFragment,
  ...
}

E3-ReleaseMessage ::= SEQUENCE {
  dAppIdentifier E3-DAppID,
  ...
}

E3-MessageAck ::= SEQUENCE {
  requestId    E3-MessageID,
  responseCode E3-ResponseCode,
  ...,
  cause        E3-Cause OPTIONAL,
  detail       E3-Text OPTIONAL
}

E3-PDU ::= SEQUENCE {
  id        E3-MessageID,
  msg CHOICE {
    setupRequest         E3-SetupRequest,
    setupResponse        E3-SetupResponse,
    subscriptionRequest  E3-SubscriptionRequest,
    subscriptionDelete   E3-SubscriptionDelete,
    subscriptionResponse E3-SubscriptionResponse,
    indicationMessage    E3-IndicationMessage,
    dAppControlAction    E3-DAppControlAction,
    dAppReport           E3-DAppReport,
    xAppControlAction    E3-XAppControlAction,
    releaseMessage       E3-ReleaseMessage,
    messageAck           E3-MessageAck,
    controlResponse      E3-ControlResponse,
    ...
  },
  ...,
  -- Native additions belong after the extension marker: keep legacy ID bits
  -- unchanged. The separate libe3 codec retains libe3's root placement.
  timestamp E3-Timestamp OPTIONAL
}

END
